(defun c:test(/ doc lay)
  (vl-load-com)
  (setq doc (vla-get-activedocument (vlax-get-acad-object)))
  (vlax-for lay (vla-get-layouts doc)
    (or (= (vla-get-name lay) "Model")
      (progn
	(vla-refreshplotdeviceinfo lay)
	(princ (strcat "\nLayout : " (vla-get-name lay)))
	(princ (strcat "\nPlotter : " (vla-get-configname lay)))
	(princ "\nPaper size :")
	(mapcar '(lambda (x) (princ (strcat "\n\t\t" (vla-getlocalemedianame lay x)))) (vlax-invoke lay 'getcanonicalmedianames))
	(terpri)
      )
    )
  )
  (princ)
)
